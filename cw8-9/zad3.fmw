FME workspace zad3.fmw

Parameters:
- SourceDataset_GEOTIFF = ""$(FME_MF_DIR)ras250_gb\fme\GEOTIFF.tif" "$(FME_MF_DIR)ras250_gb\fme\GEOTIFF_1.tif" "$(FME_MF_DIR)ras250_gb\fme\GEOTIFF_2.tif" "$(FME_MF_DIR)ras250_gb\fme\GEOTIFF_3.tif" "$(FME_MF_DIR)ras250_gb\fme\GEOTIFF_4.tif" "$(FME_MF_DIR)ras250_gb\fme\GEOTIFF_5.tif" "$(FME_MF_DIR)ras250_gb\fme\GEOTIFF_6.tif" "$(FME_MF_DIR)ras250_gb\fme\GEOTIFF_7.tif" "$(FME_MF_DIR)ras250_gb\fme\GEOTIFF_8.tif" "$(FME_MF_DIR)ras250_gb\fme\GEOTIFF_9.tif" "$(FME_MF_DIR)ras250_gb\fme\GEOTIFF_10.tif" "$(FME_MF_DIR)ras250_gb\fme\GEOTIFF_11.tif" "$(FME_MF_DIR)ras250_gb\fme\GEOTIFF_12.tif" "$(FME_MF_DIR)ras250_gb\fme\GEOTIFF_13.tif" "$(FME_MF_DIR)ras250_gb\fme\GEOTIFF_14.tif" "$(FME_MF_DIR)ras250_gb\fme\GEOTIFF_15.tif" "$(FME_MF_DIR)ras250_gb\fme\GEOTIFF_16.tif" "$(FME_MF_DIR)ras250_gb\fme\GEOTIFF_17.tif" "$(FME_MF_DIR)ras250_gb\fme\GEOTIFF_18.tif" "$(FME_MF_DIR)ras250_gb\fme\GEOTIFF_19.tif" "$(FME_MF_DIR)ras250_gb\fme\GEOTIFF_20.tif" "$(FME_MF_DIR)ras250_gb\fme\GEOTIFF_21.tif" "$(FME_MF_DIR)ras250_gb\fme\GEOTIFF_22.tif" "$(FME_MF_DIR)ras250_gb\fme\GEOTIFF_23.tif" "$(FME_MF_DIR)ras250_gb\fme\GEOTIFF_24.tif" "$(FME_MF_DIR)ras250_gb\fme\GEOTIFF_25.tif" "$(FME_MF_DIR)ras250_gb\fme\GEOTIFF_26.tif" "$(FME_MF_DIR)ras250_gb\fme\GEOTIFF_27.tif" "$(FME_MF_DIR)ras250_gb\fme\GEOTIFF_28.tif" "$(FME_MF_DIR)ras250_gb\fme\GEOTIFF_29.tif" "$(FME_MF_DIR)ras250_gb\fme\GEOTIFF_30.tif" "$(FME_MF_DIR)ras250_gb\fme\GEOTIFF_31.tif" "$(FME_MF_DIR)ras250_gb\fme\GEOTIFF_32.tif" "$(FME_MF_DIR)ras250_gb\fme\GEOTIFF_33.tif" "$(FME_MF_DIR)ras250_gb\fme\GEOTIFF_34.tif" "$(FME_MF_DIR)ras250_gb\fme\GEOTIFF_35.tif" "$(FME_MF_DIR)ras250_gb\fme\GEOTIFF_36.tif" "$(FME_MF_DIR)ras250_gb\fme\GEOTIFF_37.tif" "$(FME_MF_DIR)ras250_gb\fme\GEOTIFF_38.tif" "$(FME_MF_DIR)ras250_gb\fme\GEOTIFF_39.tif" "$(FME_MF_DIR)ras250_gb\fme\GEOTIFF_40.tif" "$(FME_MF_DIR)ras250_gb\fme\GEOTIFF_41.tif" "$(FME_MF_DIR)ras250_gb\fme\GEOTIFF_42.tif" "$(FME_MF_DIR)ras250_gb\fme\GEOTIFF_43.tif" "$(FME_MF_DIR)ras250_gb\fme\GEOTIFF_44.tif" "$(FME_MF_DIR)ras250_gb\fme\GEOTIFF_45.tif" "$(FME_MF_DIR)ras250_gb\fme\GEOTIFF_46.tif" "$(FME_MF_DIR)ras250_gb\fme\GEOTIFF_47.tif" "$(FME_MF_DIR)ras250_gb\fme\GEOTIFF_48.tif" "$(FME_MF_DIR)ras250_gb\fme\GEOTIFF_49.tif" "$(FME_MF_DIR)ras250_gb\fme\GEOTIFF_50.tif" "$(FME_MF_DIR)ras250_gb\fme\GEOTIFF_51.tif" "$(FME_MF_DIR)ras250_gb\fme\GEOTIFF_52.tif" "$(FME_MF_DIR)ras250_gb\fme\GEOTIFF_53.tif" "$(FME_MF_DIR)ras250_gb\fme\GEOTIFF_54.tif" "$(FME_MF_DIR)ras250_gb\fme\GEOTIFF_55.tif""   # Source GeoTIFF File(s) or URL(s)
- SourceDataset_SHAPEFILE = $(FME_MF_DIR)GB\scotland_and_wales_region.shp   # Source Esri Shapefile(s)
- DestDataset_POSTGIS = postgres   # Connection

Readers:
- GEOTIFF_1: GEOTIFF from $(SourceDataset_GEOTIFF) in EPSG:4326
- SHAPEFILE_1: SHAPEFILE from $(SourceDataset_SHAPEFILE)

Writers:
- POSTGIS_1: POSTGIS to $(DestDataset_POSTGIS)

scotland_and_wales_region (reader SHAPEFILE_1)
    attributes: NAME varchar(100), AREA_CODE varchar(3), DESCRIPTIO varchar(50), FILE_NAME varchar(100), NUMBER number(11,0), NUMBER0 number(11,0), POLYGON_ID number(11,0), UNIT_ID number(11,0), CODE varchar(9), HECTARES float, AREA float, TYPE_CODE varchar(2), DESCRIPT0 varchar(25), TYPE_COD0 varchar(3), DESCRIPT1 varchar(36)
    -> Tester
Tester
    BOOL_OP = OR
    TEST_CLAUSE = CASE_INSENSITIVE_TEST @Value(NAME) BEGINS_WITH South Wales
    TEST_MODE = CASE_INSENSITIVE_TEST
    PASSED -> Reprojector
Reprojector
    DEST = EPSG:4326
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Aggregator
Aggregator
    ACCUM_ATTRS_NAME = Drop Incoming Attributes
    AGGREGATE_TYPE = Homogeneous Collection (If Possible)
    MODE = Geometry - Assemble One Level
    SEP = ,
    AGGREGATE -> Clipper [CLIPPER]
GEOTIFF (reader GEOTIFF_1)
    -> Clipper [CANDIDATE]
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> RasterPaletteResolver
RasterPaletteResolver
    -> Exports (writer POSTGIS_1)
Exports (writer POSTGIS_1)
    attributes: _clipped char(3)
